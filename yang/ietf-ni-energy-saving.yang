module ietf-ni-energy-saving {
  yang-version 1.1;
  namespace "urn:ietf:params:xml:ns:yang:ietf-ni-energy-saving";
  prefix esm-ni;

  import ietf-energy-efficiency-common {
    prefix esm-common;
    reference
      "RFC XXXX: YANG Data Models for Energy Saving Management";
  }
  import ietf-network-inventory {
    prefix ni;
    reference
      "RFC IIII: A YANG Data Model for Network Inventory";
  }

  organization
    "IETF xxx Working Group.";
  contact
    "WG Web:   <https://datatracker.ietf.org/wg/xxx/>;
     WG List:  <mailto:xxxx@ietf.org>

     Author:   Gen Chen
               <mailto:chengen@huawei.com>
     Editor:   Qin Wu
               <mailto:bill.wu@huawei.com>
     Editor:   Mohamed Boucadair
               <mailto:mohamed.boucadair@orange.com>
     Author:   Carlos Pignataro
               <mailto:cpignata@gmail.com>";
  description
    "This module contains a collection of YANG definitions for power
     and energy management of devices. It also augments both the
     network topology and inventory models.

     Copyright (c) 2024 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2024-01-23 {
    description
      "Initial revision.";
    reference
      "RFC XXXX: YANG Data Models for Energy Saving Management";
  }

  grouping network-element-ref {
    description
      "Contains the information necessary to reference a network
       element.";
    leaf ne-ref {
      type leafref {
        path "/ni:network-inventory/ni:network-elements"
           + "/ni:network-element/ni:ne-id";
        require-instance false;
      }
      description
        "Used to reference a network element.";
    }
  }

  grouping component-ref {
    description
      "Contains the information necessary to reference a component.";
    leaf node-ref {
      type leafref {
        path "/ni:network-inventory/ni:network-elements"
           + "/ni:network-element[ni:ne-id="
           + "current()/../ne-ref]/ni:components/ni:component"
           + "/ni:component-id";
        require-instance false;
      }
      description
        "Used to reference a component.";
    }
    uses network-element-ref;
  }

  augment "/ni:network-inventory/ni:network-elements"
        + "/ni:network-element" {
    if-feature "esm-common:energy-saving";
    description
      "Energy management static data for network element.";
    container energy-management {
      config false;
      description
        "Statistics of the energy management.";
      leaf energy-monitoring-capability {
        type boolean;
        description
          "Indicates whether monitoring can be performed.";
      }
      container energy-saving-modes {
        description
          "List of supported energy saving modes.";
        uses esm-common:energy-saving-modes;
      }
    }
  }

  augment "/ni:network-inventory/ni:network-elements"
        + "/ni:network-element/ni:components/ni:component" {
    if-feature "esm-common:energy-saving";
    description
      "Energy management static data for component.";
    container power-parameters {
      config false;
      description
        "Power parameter monitoring.";
      uses esm-common:power-parameters;
    }
  }
}
